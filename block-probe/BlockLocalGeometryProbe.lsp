; Load after BlockDefinitionProbe.lsp. Independent, getter-only local diagnostic.
(defun blp:abort (message) (princ (strcat "\n" message)) (quit))
(defun blp:overlap (lo hi center half)
  (and (<= (car lo) (+ (car center) half))
       (>= (car hi) (- (car center) half))
       (<= (cadr lo) (+ (cadr center) half))
       (>= (cadr hi) (- (cadr center) half))))
(defun blp:bounds (obj / lo hi)
  (vla-GetBoundingBox obj 'lo 'hi)
  (list (vlax-safearray->list lo) (vlax-safearray->list hi)))
(defun blp:normalize-handle (value)
  (strcase (vl-string-trim " \t\r\n" value)))
; Pure decision table, tested separately from AutoCAD getters.
(defun blp:anchor-status (tr-found global-found owner-ok same-record has10 transform-ok)
  (cond
    ((and (not tr-found) (not global-found)) "handle_not_found")
    ((not owner-ok) "owner_mismatch")
    ((or (not tr-found) (not global-found) (not same-record)) "traversal_handent_disagreement")
    ((not has10) "missing_dxf10")
    ((not transform-ok) "coordinate_transform_error")
    (T "resolved")))
(defun blp:diag (key value)
  (setq anchorDiagnostics (append anchorDiagnostics (list (cons key value))))
  (princ (strcat "\n" key "=" (bp:fmt value))))
(defun blp:owner (d / owner)
  (setq owner (cdr (assoc 330 d)))
  (if owner (cdr (assoc 5 (entget owner)))))
(defun blp:identity (d)
  (list (cdr (assoc 0 d)) (cdr (assoc 5 d)) (blp:owner d)
        (cdr (assoc 10 d)) (cdr (assoc 11 d)) (cdr (assoc 210 d))))
(defun blp:anchor-record (prefix d)
  (blp:diag (strcat prefix "Found") (if d T nil))
  (blp:diag (strcat prefix "EntityType") (cdr (assoc 0 d)))
  (blp:diag (strcat prefix "Handle") (cdr (assoc 5 d)))
  (blp:diag (strcat prefix "OwnerHandle") (blp:owner d))
  (blp:diag (strcat prefix "DXF10_RAW") (cdr (assoc 10 d)))
  (blp:diag (strcat prefix "DXF11_RAW") (cdr (assoc 11 d)))
  (blp:diag (strcat prefix "DXF210_RAW") (cdr (assoc 210 d)))
  (blp:diag (strcat prefix "Text_RAW") (cdr (assoc 1 d))))
(defun blp:point3-p (point)
  (and (listp point) (= (length point) 3)
       (numberp (car point)) (numberp (cadr point)) (numberp (caddr point))))
(defun blp:coordinate-method (typ normal)
  (cond
    ((member typ '("LINE" "MTEXT")) "identity_definition_coordinates")
    ((not (member typ '("TEXT" "ATTDEF" "CIRCLE" "ARC" "INSERT"))) "unsupported_coordinate_semantics")
    ((not normal) "missing_normal")
    ((and (equal typ "TEXT") (equal normal '(0 0 1))) "identity_ocs_to_definition")
    (T "trans_normal_to_definition")))
(defun blp:transform-outcome (valid exception result)
  (cond (exception (list "coordinate_transform_error" nil exception))
        (valid (list "resolved" result nil))
        (T (list "invalid_transform_result" nil nil))))
(defun blp:resolve-coordinate (d / input normal method status exception point result outcome)
  (setq input (cdr (assoc 10 d)) normal (cdr (assoc 210 d))
        method (blp:coordinate-method (cdr (assoc 0 d)) normal) status "resolved")
  (blp:diag "DXF10_RAW" input) (blp:diag "DXF11_RAW" (cdr (assoc 11 d)))
  (blp:diag "DXF210_RAW" normal)
  (blp:diag "RawCoordinateSystem"
    (cond ((member (cdr (assoc 0 d)) '("LINE" "MTEXT")) "definition_cartesian")
          ((= method "unsupported_coordinate_semantics") "unknown") (T "entity_ocs")))
  (blp:diag "CoordinateInput" input)
  (blp:diag "CoordinateResolutionMethod" method)
  (blp:diag "InstanceWCS" "not_computed")
  (cond
    ((not (blp:point3-p input)) (setq status "invalid_dxf10"))
    ((member method '("missing_normal" "unsupported_coordinate_semantics")) (setq status method))
    ((member method '("identity_ocs_to_definition" "identity_definition_coordinates"))
      (setq point input))
    ((or (not (blp:point3-p normal)) (equal normal '(0 0 0))) (setq status "invalid_normal"))
    (T
      ; Axis normalization only. No INSERT path, placement or base-point transform.
      (blp:diag "Trans.Point" input)
      (blp:diag "Trans.FromType" (type normal)) (blp:diag "Trans.FromValue" normal)
      (blp:diag "Trans.ToType" (type 0)) (blp:diag "Trans.ToValue" 0)
      (setq result (vl-catch-all-apply 'trans (list input normal 0)))
      (if (vl-catch-all-error-p result)
        (setq exception (vl-catch-all-error-message result) result nil))
      (blp:diag "Trans.Return_RAW" result)
      (setq outcome (blp:transform-outcome (blp:point3-p result) exception result)
            status (car outcome) point (cadr outcome) exception (caddr outcome))))
  (blp:diag "CoordinateException_RAW" exception)
  (blp:diag "CoordinateResolutionStatus" status)
  (blp:diag "AnchorPoint_DefinitionLocal" point)
  (list status point))
; GetBoundingBox is documented as WCS. For direct definition entities, establish
; the database frame at runtime using zero-thickness LINE DXF endpoints as controls.
; No inference from the containing INSERT's insertion point is used.
(defun blp:frame-status (hasControls hasMismatch)
  (cond (hasMismatch "coordinate_frame_mismatch")
        (hasControls "verified_definition_line_extents")
        (T "unverified_no_control_geometry")))
(defun blp:frame-bounds-match (wanted actual ownerOK tolerance)
  (and ownerOK (equal wanted actual tolerance)))
(defun blp:verify-frame (block / obj d a b box expected wanted controls mismatch status tolerance)
  (setq controls 0 tolerance 0.00001 expected (vla-get-Handle block))
  (vlax-for obj block
    (setq d (entget (vlax-vla-object->ename obj)))
    (if (and (= (cdr (assoc 0 d)) "LINE")
             (or (not (assoc 39 d)) (= (cdr (assoc 39 d)) 0))
             (blp:point3-p (cdr (assoc 10 d))) (blp:point3-p (cdr (assoc 11 d))))
      (progn
        (setq a (cdr (assoc 10 d)) b (cdr (assoc 11 d))
              wanted (list (mapcar 'min a b) (mapcar 'max a b))
              box (vl-catch-all-apply 'blp:bounds (list obj)))
        (if (vl-catch-all-error-p box)
          (progn (setq mismatch T)
            (blp:diag "FrameControlHandle" (cdr (assoc 5 d)))
            (blp:diag "FrameControlError" (vl-catch-all-error-message box)))
          (progn
            (setq controls (1+ controls))
            (if (or (= controls 1) (not (blp:frame-bounds-match wanted box (equal (blp:owner d) expected) tolerance)))
              (progn
                (blp:diag "FrameControlHandle" (cdr (assoc 5 d)))
                (blp:diag "FrameControlDefinitionBounds" wanted)
                (blp:diag "FrameControlGetterBounds" box)))
            (if (not (blp:frame-bounds-match wanted box (equal (blp:owner d) expected) tolerance))
              (setq mismatch T)))))))
  (setq status (blp:frame-status (> controls 0) mismatch))
  (blp:diag "BoundingBoxFrameStatus" status)
  (blp:diag "BoundingBoxFrameControlCount" controls)
  (blp:diag "BoundingBoxFrameTolerance" tolerance)
  (blp:diag "BoundingBoxFrameBasis" "direct definition objects; compare zero-thickness LINE raw endpoint extents with getter; no instance transform")
  status)
(defun blp:traverse-anchor (block handle / obj d found count)
  (setq count 0)
  (vlax-for obj block
    (setq count (1+ count) d (entget (vlax-vla-object->ename obj)))
    (if (equal handle (blp:normalize-handle (cdr (assoc 5 d)))) (setq found d)))
  (blp:diag "TraversalEntityCount" count)
  found)
(defun blp:global-anchor (handle / entity)
  (setq entity (handent handle))
  (if entity (entget entity)))
(defun blp:anchor (block handle / tr glob expected owner-ok same status point result getter-error)
  (setq expected (vla-get-Handle block))
  (setq tr (vl-catch-all-apply 'blp:traverse-anchor (list block handle)))
  (if (vl-catch-all-error-p tr)
    (progn (blp:diag "TraversalError" (vl-catch-all-error-message tr))
      (setq tr nil getter-error T)))
  (setq glob (vl-catch-all-apply 'blp:global-anchor (list handle)))
  (if (vl-catch-all-error-p glob)
    (progn (blp:diag "HandentError" (vl-catch-all-error-message glob))
      (setq glob nil getter-error T)))
  (blp:anchor-record "Traversal." tr)
  (blp:anchor-record "Handent." glob)
  (setq owner-ok (and (or (not tr) (equal (blp:owner tr) expected))
                      (or (not glob) (equal (blp:owner glob) expected)))
        same (and tr glob (equal (cdr (assoc -1 tr)) (cdr (assoc -1 glob)))
                  (equal (blp:identity tr) (blp:identity glob))))
  (setq status (if getter-error "traversal_handent_disagreement"
    (blp:anchor-status tr glob owner-ok same (assoc 10 tr) T)))
  (if (= status "resolved")
    (progn
      (setq result (blp:resolve-coordinate tr))
      (if (= (car result) "resolved") (setq point (cadr result))
        (setq status "coordinate_transform_error"))))
  (blp:diag "AnchorStatus" status)
  (blp:diag "AnchorResolutionMethod" "direct traversal AND handent; same entity and requested owner required")
  (if (= status "resolved")
    (progn (blp:anchor-record "Anchor." tr) (blp:diag "AnchorTransformedLocalCoordinate" point)))
  (blp:diag "SnapshotComparisonStatus" "not_automatically_compared; compare runtime identity with source index; preserve discrepancies")
  (list status point))
(defun blp:scan (block center half / obj d box selected unknown scanned result)
  (setq selected 0 unknown 0 scanned 0)
  (vlax-for obj block
    (setq scanned (1+ scanned) d (entget (vlax-vla-object->ename obj)))
    (setq box (vl-catch-all-apply 'blp:bounds (list obj)))
    ; Unknown extents retained even outside window: absence cannot be established.
    (if (or (vl-catch-all-error-p box) (blp:overlap (car box) (cadr box) center half))
      (progn
        (setq selected (1+ selected))
        (bp:out "LocalEntity_BEGIN")
        (bp:val "SourceBlock" (vla-get-Name block))
        (bp:val "SourceHandle" (cdr (assoc 5 d)))
        (if (vl-catch-all-error-p box)
          (progn (setq unknown (1+ unknown) errors (1+ errors))
            (bp:val "WindowMembership" "unknown")
            (bp:val "BoundsError" (vl-catch-all-error-message box)))
          (progn (bp:val "WindowMembership" "bbox_overlap_candidate")
            (bp:val "BoundsMin" (car box)) (bp:val "BoundsMax" (cadr box))))
        (bp:val "GeometryStatus"
          (if (member (cdr (assoc 0 d)) '("LINE" "LWPOLYLINE" "CIRCLE" "ARC" "INSERT" "TEXT" "MTEXT" "ATTDEF"))
            "raw_dxf_only" "unknown"))
        (setq result (vl-catch-all-apply 'bp:entity (list obj)))
        (if (vl-catch-all-error-p result)
          (progn (setq errors (1+ errors))
            (bp:val "EntityReadStatus" "error")
            (bp:val "EntityError" (vl-catch-all-error-message result)))
          (bp:val "EntityReadStatus" "read"))
        (bp:out "LocalEntity_END"))))
  (bp:val "ScannedDirectEntityCount" scanned)
  (bp:val "SelectedEntityCount" selected)
  (bp:val "UnknownWindowCount" unknown))
(defun c:MEPBLOCKLOCALPROBE (/ *error* app doc blocks block name handle rawHandle center half basis path fh errors result item anchorDiagnostics)
  (defun *error* (msg)
    (princ (strcat "\nLocal probe stopped: " msg))
    (if fh (progn (vl-catch-all-apply 'write-line (list (strcat "INCOMPLETE_REPORT=" msg) fh))
                   (vl-catch-all-apply 'close (list fh))))
    (foreach item (list block blocks doc app)
      (if item (vl-catch-all-apply 'vlax-release-object (list item))))
    (princ))
  (vl-load-com)
  (setq app (vlax-get-acad-object) doc (vla-get-ActiveDocument app) blocks (vla-get-Blocks doc))
  (blp:diag "ProbeVersion" "1.2-definition-local")
  (blp:diag "DWG" (strcat (getvar "DWGPREFIX") (getvar "DWGNAME")))
  (setq name (getstring T "\nBlock definition name: "))
  (blp:diag "RequestedBlockDefinition" name)
  (setq block (vla-item blocks name))
  (blp:diag "ResolvedBlockDefinition" (vla-get-Name block))
  (blp:diag "BlockRecordHandle" (vla-get-Handle block))
  (if (or (= :vlax-true (vla-get-IsLayout block)) (= :vlax-true (vla-get-IsXRef block)))
    (blp:abort "Local definitions only; layouts and XREF are unsupported."))
  (setq rawHandle (getstring T "\nAnchor internal Handle <enter local XYZ manually>: ")
        handle (blp:normalize-handle rawHandle))
  (blp:diag "AnchorInput_RAW" rawHandle)
  (blp:diag "AnchorInput_Normalized" handle)
  (if (/= handle "")
    (progn (setq result (blp:anchor block handle))
      (if (/= (car result) "resolved") (blp:abort (strcat "AnchorStatus=" (car result))))
      (setq center (cadr result)))
    (setq center (list (getreal "\nDefinition X: ") (getreal "\nDefinition Y: ") (getreal "\nDefinition Z: "))))
  (if (not (and (numberp (car center)) (numberp (cadr center)) (numberp (caddr center))))
    (blp:abort "Invalid local coordinate."))
  (setq result (blp:verify-frame block))
  (if (/= result "verified_definition_line_extents")
    (blp:abort (strcat "BoundingBoxFrameStatus=" result "; window comparison not performed.")))
  (initget 7) (setq half (getreal "\nXY square window half-size (drawing units): "))
  (setq basis (getstring T "\nWindow selection evidence/reason: "))
  (setq path (getfiled "Save NEW block-local-geometry-probe.txt"
    (strcat (getvar "DWGPREFIX") "block-local-geometry-probe.txt") "txt" 1))
  (if path
    (cond
      ((findfile path) (princ (strcat "\nExisting snapshot protected: " path)))
      ((/= (strcase (strcat (vl-filename-base path) (vl-filename-extension path))) "BLOCK-LOCAL-GEOMETRY-PROBE.TXT")
        (princ "\nUnexpected filename; cancelled."))
      (T
        (setq fh (if (= 0 (getvar "LISPSYS")) (open path "w") (open path "w" "utf8-bom")))
        (if (not fh) (blp:abort "Cannot open output."))
        (setq errors 0)
        (foreach item anchorDiagnostics (bp:val (car item) (cdr item)))
        (bp:val "AcquiredAtLocal" (getvar "CDATE"))
        (bp:val "SourceBlock" name) (bp:raw "DefinitionDXF:" (tblsearch "BLOCK" name))
        (bp:val "AnchorHandle" handle) (bp:val "AnchorPoint" center)
        (bp:val "WindowHalfSize" half) (bp:val "WindowSelectionBasis" basis)
        (bp:val "WindowScope" "window_scope_uncertain")
        (bp:val "WindowMethod" "XY definition-space axis-aligned bounding-box overlap; Z unfiltered; no clipping")
        (bp:val "Coverage" "direct entities only; nested INSERT transforms retained, not expanded")
        (bp:val "Limitations" "bbox overlap is not containment, visibility, equipment binding or engineering connection; unknown extents retained")
        (blp:scan block center half)
        (bp:val "ReadErrorCount" errors) (bp:out "END_OF_REPORT")
        (close fh) (setq fh nil)
        (princ (strcat "\nReport saved: " path)))))
  (foreach item (list block blocks doc app) (if item (vlax-release-object item)))
  (princ))
(princ "\nLoaded MEPBLOCKLOCALPROBE. Requires BlockDefinitionProbe.lsp loaded first.")
(princ)
