; Independent diagnostic. Read getters only; no changes to the main extractor.
(defun bp:out (s) (write-line s fh))
(defun bp:fmt (v / s tail)
  (cond
    ((= (type v) 'REAL) (rtos v 2 12))
    ((and v (listp v))
      (setq s (strcat "(" (bp:fmt (car v))) tail (cdr v))
      (while (and tail (listp tail)) (setq s (strcat s " " (bp:fmt (car tail))) tail (cdr tail)))
      (if tail (setq s (strcat s " . " (bp:fmt tail))))
      (strcat s ")"))
    (T (vl-prin1-to-string v))))
(defun bp:val (k v) (bp:out (strcat k "=" (bp:fmt v))))
(defun bp:raw (prefix d / p)
  (foreach p d
    (if (member (car p) '(310 311 312 313 314 315 316 317 318 319))
      (bp:val "BinaryDXFOmitted" (car p))
      (bp:out (strcat prefix (itoa (car p)) "=" (bp:fmt (cdr p)))))))
(defun bp:entity (obj / e d layer sub sd)
  (setq e (vlax-vla-object->ename obj) d (entget e))
  (bp:val "EntityHandle" (cdr (assoc 5 d)))
  (bp:val "DXF_Type" (cdr (assoc 0 d)))
  (bp:val "Layer" (cdr (assoc 8 d)))
  (bp:val "ColorSource"
    (cond ((assoc 420 d) "TrueColor") ((assoc 430 d) "ColorBook")
      ((= 0 (cdr (assoc 62 d))) "ByBlock")
      ((or (not (assoc 62 d)) (= 256 (cdr (assoc 62 d)))) "ByLayer")
      (T "ACI")))
  (bp:val "DXF60" (if (assoc 60 d) (cdr (assoc 60 d)) 0))
  (bp:val "Linetype" (if (assoc 6 d) (cdr (assoc 6 d)) "BYLAYER"))
  (bp:val "Lineweight_DXF370" (if (assoc 370 d) (cdr (assoc 370 d)) -1))
  (bp:val "LocalCoordinates" "raw entity OCS/block-definition coordinates; not WCS")
  (bp:val "VisibilityInterpretation" "DXF60 only; does not prove evaluated dynamic visibility")
  (if (= (cdr (assoc 0 d)) "INSERT")
    (bp:val "ReferencedBlockName" (cdr (assoc 2 d))))
  (bp:raw "DXF:" d)
  (setq layer (tblsearch "LAYER" (cdr (assoc 8 d))))
  (bp:raw "LayerDXF:" layer)
  ; POLYLINE vertices and attached attributes are owned subentities, not nested blocks.
  (if (or (= (cdr (assoc 0 d)) "POLYLINE")
          (and (= (cdr (assoc 0 d)) "INSERT") (= 1 (cdr (assoc 66 d)))))
    (progn
      (setq sub (entnext e))
      (while (and sub (/= "SEQEND" (cdr (assoc 0 (setq sd (entget sub))))))
        (bp:out "Subentity_BEGIN") (bp:raw "DXF:" sd) (bp:out "Subentity_END")
        (setq sub (entnext sub)))))
  (bp:out "Entity_END"))
(defun bp:bounds (obj / lo hi)
  (vla-GetBoundingBox obj 'lo 'hi)
  (list (vlax-safearray->list lo) (vlax-safearray->list hi)))
(defun bp:one-entity (obj / d result)
  (setq d (entget (vlax-vla-object->ename obj)))
  (bp:val "SourceDefinitionPath" onePath)
  (bp:val "SourceInternalHandle" (cdr (assoc 5 d)))
  (bp:val "InstanceScope" "definition path only; ModelSpace instance unresolved")
  (bp:val "SemanticStatus" "unknown; raw identity retained")
  (bp:val "BoundsFrame" "direct definition object getter; no instance transform; not independently frame-verified")
  (setq result (vl-catch-all-apply 'bp:bounds (list obj)))
  (if (vl-catch-all-error-p result)
    (progn (setq errors (1+ errors))
      (bp:val "BoundsStatus" "unknown")
      (bp:val "BoundsError" (vl-catch-all-error-message result)))
    (progn (bp:val "BoundsStatus" "read")
      (bp:val "BoundsMin" (car result)) (bp:val "BoundsMax" (cadr result))))
  (if (member (cdr (assoc 0 d)) '("LWPOLYLINE" "POLYLINE"))
    (bp:val "Closed_RAW" (= 1 (logand 1 (if (assoc 70 d) (cdr (assoc 70 d)) 0)))))
  (bp:entity obj))
(defun bp:block (name / block obj result count)
  (bp:val "Block_BEGIN" name)
  (setq block (vl-catch-all-apply 'vla-item (list blocks name)))
  (if (vl-catch-all-error-p block)
    (progn (setq errors (1+ errors)) (bp:val "BlockError" (vl-catch-all-error-message block)))
    (progn
      (bp:raw "DefinitionDXF:" (tblsearch "BLOCK" name))
      (setq result (vl-catch-all-apply 'vla-get-IsDynamicBlock (list block)))
      (if (vl-catch-all-error-p result)
        (progn (bp:val "DefinitionIsDynamicBlockStatus" "unavailable")
          (bp:val "DefinitionIsDynamicBlockError" (vl-catch-all-error-message result)))
        (progn (bp:val "DefinitionIsDynamicBlock" result)
          (bp:val "DefinitionIsDynamicBlockStatus" "read")))
      (setq count 0)
      (vlax-for obj block
        (setq count (1+ count))
        (setq result (vl-catch-all-apply (if oneLevel 'bp:one-entity 'bp:entity) (list obj)))
        (if (vl-catch-all-error-p result)
          (progn (setq errors (1+ errors)) (bp:val "EntityError" (vl-catch-all-error-message result)) (bp:out "Entity_END"))))
      (bp:val "DirectEntityCount" count)
      (vlax-release-object block)))
  (bp:out "Block_END"))
(defun bp:run (names / *error* fh app doc blocks path name errors)
  (defun *error* (msg)
    (princ (strcat "\nBlock probe stopped: " msg))
    (if fh (progn (vl-catch-all-apply 'write-line (list (strcat "INCOMPLETE_REPORT=" msg) fh)) (vl-catch-all-apply 'close (list fh))))
    (if blocks (vl-catch-all-apply 'vlax-release-object (list blocks)))
    (if doc (vl-catch-all-apply 'vlax-release-object (list doc)))
    (if app (vl-catch-all-apply 'vlax-release-object (list app))) (princ))
  (vl-load-com)
  (setq path (getfiled "Save NEW block-definition-probe.txt" (strcat (getvar "DWGPREFIX") "block-definition-probe.txt") "txt" 1))
  (if path
    (cond
      ((findfile path) (princ (strcat "\nExisting file protected: " path)))
      ((/= (strcase (strcat (vl-filename-base path) (vl-filename-extension path))) "BLOCK-DEFINITION-PROBE.TXT") (princ "\nUnexpected filename; cancelled."))
      (T
        (setq fh (if (= 0 (getvar "LISPSYS")) (open path "w") (open path "w" "utf8-bom")))
        (if fh
          (progn
            (setq errors 0 app (vlax-get-acad-object) doc (vla-get-ActiveDocument app) blocks (vla-get-Blocks doc))
            (bp:val "ProbeVersion" "1.1-target-subblocks")
            (if oneLevel
              (progn
                (bp:val "OneLevelProbeVersion" "1.0")
                (bp:val "SourceDefinitionPath" onePath)
                (bp:val "DefinitionPathStatus" onePathStatus)
                (bp:raw "ParentReferenceDXF:" parentDXF)))
            (bp:val "DWG" (strcat (getvar "DWGPREFIX") (getvar "DWGNAME")))
            (bp:val "AcquiredAtLocal" (getvar "CDATE"))
            (bp:val "RequestedBlocks" names)
            (bp:out "Nested INSERT references are recorded, not expanded")
            (bp:out "Non-binary entget DXF retained; XData/extension dictionaries and evaluated visibility not recovered")
            (foreach name names (bp:block name))
            (bp:val "ReadErrorCount" errors)
            (bp:out "END_OF_REPORT")
            (close fh) (setq fh nil)
            (vlax-release-object blocks) (setq blocks nil)
            (vlax-release-object doc) (setq doc nil)
            (vlax-release-object app) (setq app nil)
            (princ (strcat "\nReport saved: " path)))))))
  (princ))
; Explicit diagnostic lists. They do not encode engineering meaning.
(defun c:MEPBLOCKPROBE () (bp:run '("*U401" "*U402" "*U403" "*U404")))
(defun c:MEPSUBBLOCKPROBE () (bp:run '("$element$00000576" "A$C705C5744")))
(defun bp:parent-status (found typ actualName requestedName owner expected)
  (cond
    ((not found) "handle_not_found")
    ((not (equal typ "INSERT")) "entity_type_mismatch")
    ((not (equal actualName requestedName)) "referenced_block_mismatch")
    ((not (and owner expected (equal owner expected))) "owner_mismatch")
    (T "resolved")))
(defun bp:parent-record-handle (parent / app doc collection record result)
  (setq app (vlax-get-acad-object) doc (vla-get-ActiveDocument app)
        collection (vla-get-Blocks doc))
  (setq record (vl-catch-all-apply 'vla-item (list collection parent)))
  ; vla-item collection parent returns the real BlockTableRecord, not BlockBegin.
  (if (vl-catch-all-error-p record)
    (setq result record)
    (progn
      (setq result (vl-catch-all-apply 'vla-get-Handle (list record)))
      (vlax-release-object record)))
  (vlax-release-object collection) (vlax-release-object doc) (vlax-release-object app)
  result)
(defun bp:parent-diag (key value)
  (princ (strcat "\n" key "=" (bp:fmt value))))
(defun c:MEPONELEVELBLOCKPROBE (/ name parent handle pe pd owner actualOwner expected oneLevel onePath onePathStatus parentDXF)
  (vl-load-com)
  (setq name (getstring T "\nBlockDefinition: "))
  (cond
    ((not (tblsearch "BLOCK" name)) (princ "\nDefinition not found; stopped."))
    (T
      (setq parent (getstring T "\nParent BlockDefinition (blank = definition only): "))
      (if (= parent "")
        (setq onePath (list name) onePathStatus "definition_only")
        (progn
          (setq handle (strcase (vl-string-trim " \t\r\n" (getstring T "\nInternal parent INSERT Handle: "))))
          (setq pe (handent handle) pd (if pe (entget pe)))
          (setq owner (cdr (assoc 330 pd))
                actualOwner (if owner (cdr (assoc 5 (entget owner))))
                expected (vl-catch-all-apply 'bp:parent-record-handle (list parent)))
          (if (vl-catch-all-error-p expected)
            (progn (bp:parent-diag "ParentRecordReadError" (vl-catch-all-error-message expected))
              (setq expected nil)))
          (setq onePathStatus (bp:parent-status (if pd T nil) (cdr (assoc 0 pd))
                                (cdr (assoc 2 pd)) name actualOwner expected))
          (bp:parent-diag "ParentInsertHandle" handle)
          (bp:parent-diag "ActualEntityType" (cdr (assoc 0 pd)))
          (bp:parent-diag "ActualReferencedBlockName" (cdr (assoc 2 pd)))
          (bp:parent-diag "RequestedReferencedBlockName" name)
          (bp:parent-diag "ActualOwnerHandle" actualOwner)
          (bp:parent-diag "ExpectedParentBlockRecordHandle" expected)
          (bp:parent-diag "ParentPathStatus" onePathStatus)
          (if (equal onePathStatus "resolved")
            (setq onePath (list parent handle name) parentDXF pd)
            (princ "\nParent path rejected; stopped."))))
      (if onePath (progn (setq oneLevel T) (bp:run (list name))))))
  (princ))
(princ "\nLoaded MEPBLOCKPROBE (outer definitions), MEPSUBBLOCKPROBE (two target subblocks).")
(princ "\nLoaded MEPONELEVELBLOCKPROBE (any definition; optional verified parent INSERT path).")
(princ)
