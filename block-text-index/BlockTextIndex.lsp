; Independent read-only block text/reference acquisition for AutoCAD Windows.
(defun bti:fmt (v / s tail)
  (cond ((= (type v) 'REAL) (rtos v 2 12))
    ((and v (listp v))
      (setq s (strcat "(" (bti:fmt (car v))) tail (cdr v))
      (while (and tail (listp tail))
        (setq s (strcat s " " (bti:fmt (car tail))) tail (cdr tail)))
      (if tail (setq s (strcat s " . " (bti:fmt tail)))) (strcat s ")"))
    (T (vl-prin1-to-string v))))
(defun bti:fail (msg) (princ (strcat "\n" msg)) (exit))
(defun bti:out (s) (if (not (write-line s fh)) (bti:fail "Output write failed")))
(defun bti:val (k v) (bti:out (strcat k "=" (bti:fmt v))))
(defun bti:text-value (d / s p)
  (if (= "MTEXT" (cdr (assoc 0 d)))
    (progn (setq s "")
      (foreach p d (if (member (car p) '(1 3)) (setq s (strcat s (cdr p))))))
    (setq s (cdr (assoc 1 d)))) s)
(defun bti:entity (obj / d typ p)
  (setq d (entget (vlax-vla-object->ename obj)) typ (cdr (assoc 0 d)))
  (if (not d) (bti:fail "Entity DXF unavailable"))
  (setq directCount (1+ directCount))
  (cond
    ((= typ "INSERT")
      (bti:out "Reference_BEGIN")
      (bti:val "ParentBlock" name) (bti:val "SourceKind" kind)
      (bti:val "InternalHandle" (cdr (assoc 5 d)))
      (bti:val "ReferencedBlockName" (cdr (assoc 2 d)))
      (bti:val "Layer" (cdr (assoc 8 d)))
      (bti:val "LocalPoint_DXF10" (cdr (assoc 10 d)))
      (bti:val "DXF60_RAW" (cdr (assoc 60 d)))
      (bti:out "Reference_END") (setq refCount (1+ refCount)))
    ((and (= kind "block_definition") (member typ '("TEXT" "MTEXT" "ATTDEF")))
      (bti:out "Text_BEGIN")
      (bti:val "SourceBlock" name) (bti:val "InternalHandle" (cdr (assoc 5 d)))
      (bti:val "EntityType" typ) (bti:val "Layer" (cdr (assoc 8 d)))
      (bti:val "Text_RAW" (bti:text-value d))
      (bti:val "Tag_RAW" (if (= typ "ATTDEF") (cdr (assoc 2 d))))
      (bti:val "Prompt_RAW" (if (= typ "ATTDEF") (cdr (assoc 3 d))))
      (bti:val "Default_RAW" (if (= typ "ATTDEF") (cdr (assoc 1 d))))
      (bti:val "LocalPoint_DXF10" (cdr (assoc 10 d)))
      (bti:val "Alignment_DXF11" (cdr (assoc 11 d)))
      (bti:val "Normal_DXF210" (cdr (assoc 210 d)))
      (bti:val "CoordinateSemantics" "raw OCS/block definition coordinates; MTEXT 11 is direction; no instance transform")
      (bti:val "DXF60_RAW" (cdr (assoc 60 d)))
      (bti:val "AttributeFlags_DXF70_RAW" (if (= typ "ATTDEF") (cdr (assoc 70 d))))
      (bti:val "VisibilityStatus" "definition_only_not_evaluated")
      ; Retain text chunks, including embedded multiline ATTDEF data, without interpretation.
      (foreach p d (if (member (car p) '(0 1 2 3 7 10 11 40 50 60 70 71 72 73 74 100 210 280))
        (bti:val (strcat "DXF:" (itoa (car p))) (cdr p))))
      (bti:val "ReadStatus" "read") (bti:out "Text_END")
      (setq textCount (1+ textCount) blockTexts (1+ blockTexts))
      (cond ((= typ "TEXT") (setq plainCount (1+ plainCount)))
        ((= typ "MTEXT") (setq multiCount (1+ multiCount)))
        (T (setq attdefCount (1+ attdefCount)))))
    ((= typ "ACAD_PROXY_ENTITY") (setq proxyCount (1+ proxyCount)))))
(defun bti:block (block / name d flags kind external result obj directCount blockTexts before)
  (setq name (vla-get-Name block) d (tblsearch "BLOCK" name)
    flags (cdr (assoc 70 d)) directCount 0 blockTexts 0 before errors)
  (setq kind (cond ((= :vlax-true (vla-get-IsLayout block))
    (if (= (strcase name) "*MODEL_SPACE") "modelspace_top_level" "paperspace_top_level"))
    (T "block_definition")))
  (setq external (or (= :vlax-true (vla-get-IsXRef block))
    (and flags (/= 0 (logand flags 28)))))
  (setq tableCount (1+ tableCount))
  (if (= kind "block_definition") (setq definitionCount (1+ definitionCount)))
  (bti:out "Block_BEGIN") (bti:val "BlockName" name) (bti:val "Kind" kind)
  (bti:val "BlockRecordHandle" (vla-get-Handle block))
  (bti:val "Flags_RAW" flags) (bti:val "BasePoint_RAW" (cdr (assoc 10 d)))
  (bti:val "XrefPath_RAW" (cdr (assoc 1 d)))
  (bti:val "ExternalStatus" (if external "external_or_dependent_not_scanned" "local_database"))
  (if external (setq skippedCount (1+ skippedCount))
    (vlax-for obj block
      (setq result (vl-catch-all-apply 'bti:entity (list obj)))
      (if (vl-catch-all-error-p result)
        (progn (setq errors (1+ errors))
          (bti:val "EntityReadError" (vl-catch-all-error-message result))))))
  (if (> blockTexts 0) (setq textBlockCount (1+ textBlockCount)))
  (bti:val "DirectEntityCount" directCount) (bti:val "BlockTextCount" blockTexts)
  (bti:val "ReadStatus" (cond (external "not_scanned_external") ((> errors before) "partial") (T "read")))
  (bti:out "Block_END"))
(defun c:MEPBLOCKTEXTINDEX (/ *error* fh app doc blocks block result outputPath outputFileName stage
    errors tableCount definitionCount textBlockCount textCount refCount plainCount multiCount attdefCount skippedCount proxyCount)
  (defun *error* (msg)
    (princ (strcat "\nBlock text index stopped at stage [" stage "]: " msg))
    (if fh (progn (vl-catch-all-apply 'write-line (list "INCOMPLETE_REPORT" fh))
      (vl-catch-all-apply 'close (list fh))))
    (if blocks (vl-catch-all-apply 'vlax-release-object (list blocks)))
    (if doc (vl-catch-all-apply 'vlax-release-object (list doc)))
    (if app (vl-catch-all-apply 'vlax-release-object (list app))) (princ))
  (setq stage "getfiled") (vl-load-com)
  (setq outputPath (getfiled "Save NEW block-text-index.txt" (strcat (getvar "DWGPREFIX") "block-text-index.txt") "txt" 1))
  (if outputPath
    (progn
      (setq stage "path-validation")
      (if (not (and (vl-filename-directory outputPath)
        (or (= (substr outputPath 1 2) "\\\\")
          (and (= (substr outputPath 2 1) ":") (member (substr outputPath 3 1) '("\\" "/"))))))
        (bti:fail "Full output path required"))
      (setq stage "filename-validation" outputFileName (strcat (vl-filename-base outputPath)
        (if (vl-filename-extension outputPath) (vl-filename-extension outputPath) "")))
      (if (/= (strcase outputFileName) "BLOCK-TEXT-INDEX.TXT") (bti:fail "Expected block-text-index.txt"))
      (setq stage "existence-check")
      (princ (strcat "\nOutputPath = " outputPath "\nOutputFileName = " outputFileName))
      (if (findfile outputPath)
        (princ (strcat "\nExists = YES\nExisting snapshot protected:\n" outputPath))
        (progn
          (princ "\nExists = NO") (setq stage "open-output")
          (setq fh (if (= 0 (getvar "LISPSYS")) (open outputPath "w") (open outputPath "w" "utf8-bom")))
          (if (not fh) (bti:fail "Cannot open output"))
          (setq errors 0 tableCount 0 definitionCount 0 textBlockCount 0 textCount 0 refCount 0
            plainCount 0 multiCount 0 attdefCount 0 skippedCount 0 proxyCount 0
            app (vlax-get-acad-object) doc (vla-get-ActiveDocument app) blocks (vla-get-Blocks doc))
          (bti:val "IndexVersion" "1.0")
          (bti:val "AcquisitionMode" "BlockTableDirectTextAndReferences")
          (bti:val "DWG" (strcat (getvar "DWGPREFIX") (getvar "DWGNAME")))
          (bti:val "AcquiredAtLocal" (getvar "CDATE"))
          (bti:val "Encoding" (if (= 0 (getvar "LISPSYS")) "system_ansi" "utf8-bom"))
          (bti:val "Coverage" "all BlockTable records; local definitions direct TEXT/MTEXT/ATTDEF; layouts INSERT references only; external/dependent records metadata only")
          (bti:val "Limitations" "no nested geometry, no XREF loading, no proxy/TABLE recovery, no attached ATTRIB, no evaluated visibility or instance binding; multiline ATTDEF raw chunks retained")
          (setq stage "block-acquisition")
          (vlax-for block blocks
            (setq result (vl-catch-all-apply 'bti:block (list block)))
            (if (vl-catch-all-error-p result)
              (progn (setq errors (1+ errors)) (bti:val "BlockReadError" (vl-catch-all-error-message result)))))
          (setq stage "write-summary")
          (bti:val "BlockTableRecordCount" tableCount)
          (bti:val "BlockDefinitionCount" definitionCount)
          (bti:val "TextBearingBlockCount" textBlockCount)
          (bti:val "TextRecordCount" textCount)
          (bti:val "TEXTCount" plainCount) (bti:val "MTEXTCount" multiCount)
          (bti:val "ATTDEFCount" attdefCount) (bti:val "ReferenceCount" refCount)
          (bti:val "ExternalSkippedCount" skippedCount) (bti:val "ProxyEntityCount" proxyCount)
          (bti:val "ReadErrorCount" errors) (bti:out "END_OF_REPORT")
          (setq stage "close-output") (close fh) (setq fh nil)
          (vlax-release-object blocks) (setq blocks nil)
          (vlax-release-object doc) (setq doc nil)
          (vlax-release-object app) (setq app nil)
          (princ (strcat "\nReport saved: " outputPath "\nText records: " (itoa textCount) "; errors: " (itoa errors)))))))
  (princ))
(princ "\nLoaded MEPBLOCKTEXTINDEX (read-only block text and reference index).")
(princ)
