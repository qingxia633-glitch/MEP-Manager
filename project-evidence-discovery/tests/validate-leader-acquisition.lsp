; ONLY run in an isolated empty validation drawing. Creates synthetic CAD entities.
(vl-load-com)
(setvar "CMDECHO" 0)
(setq validation-line (entmakex '((0 . "LINE") (100 . "AcDbEntity") (100 . "AcDbLine") (10 0.0 0.0 0.0) (11 10.0 0.0 0.0))))
(setq validation-text (entmakex '((0 . "MTEXT") (100 . "AcDbEntity") (100 . "AcDbMText") (10 5.0 5.0 0.0) (40 . 1.0) (41 . 10.0) (1 . "S") (71 . 1))))
(setq validation-leader (entmakex (list '(0 . "LEADER") '(100 . "AcDbEntity") '(100 . "AcDbLeader") '(3 . "Standard") '(71 . 1) '(72 . 0) '(73 . 0) '(74 . 0) '(75 . 0) '(76 . 2) '(10 5.0 0.0 0.0) '(10 5.0 5.0 0.0) '(210 0.0 0.0 1.0) (cons 340 validation-text))))
(command "_.MLEADER" '(20.0 0.0 0.0) '(25.0 5.0 0.0) "S")
(setq validation-mleader (entlast))
(setq mep2:fh (open validation-report "w") full T errors 0 stage "validation")
(mep2:val "DWG" "independent-leader-validation.dwg")
(mep2:val "AcquisitionMode" "ModelSpaceTopLevelAllLayers")
(mep2:val "ModelSpaceTopLevel" "included")
(mep2:val "NestedBlocks" "not expanded")
(mep2:val "ValidationPurpose" "AutoCAD object chain only; not project evidence")
(foreach e (list validation-line validation-text validation-leader validation-mleader)
  (if e (progn
    (setq d (entget e))
    (mep2:val "EntityHandle" (cdr (assoc 5 d)))
    (mep2:val "DXF_Type" (cdr (assoc 0 d)))
    (mep2:val "Layer" (cdr (assoc 8 d)))
    (mep2:details e d))))
(mep2:val "ReadErrorCount" errors)
(close mep2:fh)
(setq mep2:fh nil)
(princ "VALIDATION_REPORT_WRITTEN")
(princ)
