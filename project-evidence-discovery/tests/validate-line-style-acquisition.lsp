; Isolated EMPTY validation drawing only. Synthetic CAD objects, not project evidence.
; Caller supplies validation-report. Uses production mep2:details without rewriting it.
(vl-load-com)
(if (> (getvar "DBMOD") 0) (progn (princ "Nonempty/modified document; stop.") (exit)))
(if (ssget "_X" '((410 . "Model"))) (progn (princ "ModelSpace not empty; stop.") (exit)))
(entmake '((0 . "LAYER") (100 . "AcDbSymbolTableRecord") (100 . "AcDbLayerTableRecord") (2 . "STYLE_VALIDATION") (70 . 0) (62 . 2) (6 . "Continuous") (290 . 1) (370 . 25)))
(entmakex '((0 . "LINE") (100 . "AcDbEntity") (8 . "STYLE_VALIDATION") (62 . 3) (6 . "Continuous") (48 . 2.0) (370 . 35) (100 . "AcDbLine") (10 0.0 0.0 0.0) (11 10.0 0.0 0.0)))
(entmakex '((0 . "LWPOLYLINE") (100 . "AcDbEntity") (8 . "STYLE_VALIDATION") (62 . 4) (6 . "Continuous") (48 . 1.5) (370 . 50) (100 . "AcDbPolyline") (90 . 2) (70 . 128) (10 0.0 5.0) (40 . 1.0) (41 . 2.0) (10 10.0 5.0) (40 . 2.0) (41 . 3.0)))
(entmakex '((0 . "ARC") (100 . "AcDbEntity") (8 . "STYLE_VALIDATION") (62 . 1) (420 . 795192) (100 . "AcDbCircle") (10 20.0 0.0 0.0) (40 . 5.0) (210 0.0 0.0 1.0) (100 . "AcDbArc") (50 . 0.0) (51 . 1.570796326794897)))
(setq mep2:fh (open validation-report "w") full T stage "style-validation" errors 0)
(mep2:val "ExtractorVersion" "2.5-line-style-evidence-v1")
(mep2:val "LineStyleContractVersion" "1")
(mep2:val "DWG" "isolated-line-style-validation.dwg")
(mep2:val "ValidationPurpose" "isolated AutoCAD object capability; NOT project evidence or real benchmark")
(mep2:val "AcquisitionMode" "ModelSpaceTopLevelAllLayers")
(mep2:val "ModelSpaceTopLevel" "included")
(mep2:val "AllLayers" "included; including off/frozen")
(mep2:val "NestedBlocks" "not expanded")
(mep2:val "XrefContents" "not expanded")
(mep2:val "PaperSpaceLayouts" "not included")
(setq style-ss (ssget "_X" '((410 . "Model"))) style-i 0)
(repeat (sslength style-ss)
  (setq style-e (ssname style-ss style-i) style-i (1+ style-i) style-d (entget style-e))
  (mep2:val "EntityHandle" (cdr (assoc 5 style-d)))
  (mep2:val "DXF_Type" (cdr (assoc 0 style-d)))
  (mep2:val "Layer" (cdr (assoc 8 style-d)))
  (mep2:details style-e style-d))
(mep2:val "ReadErrorCount" errors)
(mep2:out "END_OF_REPORT: scan finished. Inspect errors and scope limitations before interpreting results.")
(close mep2:fh)
(setq mep2:fh nil)
(princ "STYLE_VALIDATION_WRITTEN")
(princ)
