; ASCII source. Read-only inspection; no external COM attachment or DWG writes.
; Native entget is primary. Optional ActiveX getters add dynamic metadata in full mode.
(defun mep2:out (s / previousStage)
  (setq previousStage stage)
  (if full (setq stage "write-output"))
  (write-line s mep2:fh)
  (setq stage previousStage))
; Decimal output independent of zero suppression, without changing DIMZIN.
(defun mep2:decimal (n / s dot)
  (setq s (rtos n 2 6))
  (if (= (substr s 1 1) ".") (setq s (strcat "0" s)))
  (if (= (substr s 1 2) "-.") (setq s (strcat "-0" (substr s 2))))
  (setq dot (vl-string-search "." s))
  (if (not dot)
    (setq s (strcat s ".") dot (1- (strlen s))))
  (while (< (- (strlen s) dot 1) 6) (setq s (strcat s "0")))
  s)
; Preserve DXF list/dotted-pair structure, including coordinates nested in raw records.
(defun mep2:format (value / s tail)
  (cond
    ((= (type value) 'REAL) (mep2:decimal value))
    ((and value (listp value))
      (setq s (strcat "(" (mep2:format (car value))) tail (cdr value))
      (while (and tail (listp tail))
        (setq s (strcat s " " (mep2:format (car tail))) tail (cdr tail)))
      (if tail (setq s (strcat s " . " (mep2:format tail))))
      (strcat s ")"))
    (T (vl-prin1-to-string value))))
(defun mep2:val (label value)
  (mep2:out (strcat label "=" (mep2:format value))))
(defun mep2:class (e / o r)
  (setq o (vl-catch-all-apply 'vlax-ename->vla-object (list e)))
  (if (vl-catch-all-error-p o)
    (strcat "UNAVAILABLE: " (vl-catch-all-error-message o))
    (progn
      (setq r (vl-catch-all-apply 'vla-get-ObjectName (list o)))
      (vl-catch-all-apply 'vlax-release-object (list o))
      (if (vl-catch-all-error-p r)
        (strcat "UNAVAILABLE: " (vl-catch-all-error-message r)) r))))
; Convert COM values without changing their CAD meaning. Preserve variant type separately.
(defun mep2:com-value (v)
  (cond
    ((= (type v) 'VARIANT) (mep2:com-value (vlax-variant-value v)))
    ((= (type v) 'SAFEARRAY) (mapcar 'mep2:com-value (vlax-safearray->list v)))
    (T v)))
(defun mep2:dynamic-field (obj prop label / raw value)
  (setq raw (vl-catch-all-apply 'vlax-get-property (list obj prop)))
  (if (vl-catch-all-error-p raw)
    (progn
      (setq dynamicPartial T)
      (mep2:val (strcat label "_Status") "unavailable")
      (mep2:val (strcat label "_Error") (vl-catch-all-error-message raw)))
    (progn
      (mep2:val (strcat label "_ValueType") (type raw))
      (if (= (type raw) 'VARIANT)
        (mep2:val (strcat label "_VariantType") (vlax-variant-type raw)))
      (setq value (vl-catch-all-apply 'mep2:com-value (list raw)))
      (if (vl-catch-all-error-p value)
        (progn (setq dynamicPartial T)
          (mep2:val (strcat label "_Status") "conversion_error")
          (mep2:val (strcat label "_Error") (vl-catch-all-error-message value)))
        (progn (mep2:val label value) (mep2:val (strcat label "_Status") "read")))))
  raw)
(defun mep2:dynamic-body (obj / dynamicFlag values prop key index)
  (mep2:dynamic-field obj 'EffectiveName "EffectiveName_RAW")
  (setq dynamicFlag (mep2:dynamic-field obj 'IsDynamicBlock "IsDynamicBlock"))
  (cond
    ((vl-catch-all-error-p dynamicFlag) (setq dynamicPartial T))
    ((= dynamicFlag :vlax-false) (mep2:val "DynamicPropertiesStatus" "not_dynamic"))
    ((= dynamicFlag :vlax-true)
      (setq values (vl-catch-all-apply 'vla-GetDynamicBlockProperties (list obj)))
      (if (vl-catch-all-error-p values)
        (progn (setq dynamicPartial T)
          (mep2:val "DynamicPropertiesStatus" "unavailable")
          (mep2:val "DynamicPropertiesError" (vl-catch-all-error-message values)))
        (progn
          (setq dynamicObjects (mep2:com-value values) index 0)
          (mep2:val "DynamicPropertyCount" (length dynamicObjects))
          (foreach prop dynamicObjects
            (mep2:val "DynamicProperty_BEGIN" index)
            (foreach key '(PropertyName Value AllowedValues UnitsType ReadOnly Description Show)
              (mep2:dynamic-field prop key (vl-symbol-name key)))
            (mep2:out "DynamicProperty_END")
            (setq index (1+ index)))
          (mep2:val "DynamicPropertiesStatus" "enumerated"))))
    (T (setq dynamicPartial T) (mep2:val "DynamicPropertiesStatus" "unknown_dynamic_flag"))))
(defun mep2:dynamic (e / obj result dynamicPartial dynamicObjects prop)
  (mep2:out "DynamicMetadata_BEGIN")
  (setq obj (vl-catch-all-apply 'vlax-ename->vla-object (list e)))
  (if (vl-catch-all-error-p obj)
    (progn
      (mep2:val "DynamicMetadataStatus" "unavailable")
      (mep2:val "DynamicMetadataError" (vl-catch-all-error-message obj)))
    (progn
      (setq result (vl-catch-all-apply 'mep2:dynamic-body (list obj)))
      (foreach prop dynamicObjects (vl-catch-all-apply 'vlax-release-object (list prop)))
      (vl-catch-all-apply 'vlax-release-object (list obj))
      (if (vl-catch-all-error-p result)
        (progn (mep2:val "DynamicMetadataStatus" "error")
          (mep2:val "DynamicMetadataError" (vl-catch-all-error-message result)))
        (mep2:val "DynamicMetadataStatus" (if dynamicPartial "partial" "read")))))
  (mep2:out "DynamicMetadata_END"))
(defun mep2:point (label p e / r)
  (mep2:val (strcat label "_OCS") p)
  (if p
    (progn
      (setq r (vl-catch-all-apply 'trans (list p e 0)))
      (if (vl-catch-all-error-p r)
        (progn
          (setq errors (1+ errors))
          (mep2:val "TRANSFORM_ERROR" (vl-catch-all-error-message r)))
        (mep2:val (strcat label "_WCS") r)))))
(defun mep2:text (d / s pair)
  (setq s "")
  (foreach pair d
    (if (= (car pair) 3) (setq s (strcat s (cdr pair)))))
  (strcat s (if (assoc 1 d) (cdr (assoc 1 d)) "")))
; Pure field maps: values are entget values (angles in radians), never roles.
; ATTRIB vertical alignment is DXF74, NOT TEXT's DXF73.
(defun mep2:layout-spec (typ)
  (cond
    ((equal typ "MTEXT")
      '(("Direction_WCS_RAW" 11) ("TextHeight" 40)
        ("ReferenceWidth" 41) ("AttachmentPoint" 71) ("TextStyle" 7)
        ("Normal" 210)))
    ((equal typ "ATTRIB")
      '(("Rotation" 50) ("TextHeight" 40) ("WidthFactor" 41)
        ("ObliqueAngle" 51) ("TextStyle" 7) ("HorizontalAlignment" 72)
        ("VerticalAlignment" 74) ("AlignmentPoint_OCS_RAW" 11) ("Normal" 210)))
    (T
      '(("Rotation" 50) ("TextHeight" 40) ("WidthFactor" 41)
        ("ObliqueAngle" 51) ("TextStyle" 7) ("HorizontalAlignment" 72)
        ("VerticalAlignment" 73) ("AlignmentPoint_OCS_RAW" 11) ("Normal" 210)))))
(defun mep2:layout-position (e d prefix / p r typ)
  (setq typ (cdr (assoc 0 d)) p (cdr (assoc 10 d)))
  (mep2:val (strcat prefix "Insertion_DXF10_RAW") p)
  (mep2:val (strcat prefix "InsertionRawFrame") (if (= typ "MTEXT") "WCS" "entity_ocs"))
  (setq r (if p (if (= typ "MTEXT") p (vl-catch-all-apply 'trans (list p e 0)))))
  (cond
    ((vl-catch-all-error-p r)
      (mep2:val (strcat prefix "positionFrame") "unknown")
      (mep2:val (strcat prefix "positionStatus") "conversion_error")
      (mep2:val (strcat prefix "positionError_RAW") (vl-catch-all-error-message r)))
    ((not r)
      (mep2:val (strcat prefix "positionFrame") "unknown")
      (mep2:val (strcat prefix "positionStatus") "missing_dxf10"))
    (T
      (mep2:val (strcat prefix "Position_WCS") r)
      (mep2:val (strcat prefix "positionFrame") "WCS")
      (mep2:val (strcat prefix "positionStatus") "read")))
  (if (and (/= typ "MTEXT") (assoc 11 d))
    (progn
      (setq r (vl-catch-all-apply 'trans (list (cdr (assoc 11 d)) e 0)))
      (if (vl-catch-all-error-p r)
        (progn
          (mep2:val (strcat prefix "AlignmentPointStatus") "conversion_error")
          (mep2:val (strcat prefix "AlignmentPointError_RAW") (vl-catch-all-error-message r)))
        (progn
          (mep2:val (strcat prefix "AlignmentPoint_WCS") r)
          (mep2:val (strcat prefix "AlignmentPointFrame") "WCS")
          (mep2:val (strcat prefix "AlignmentPointStatus") "read"))))))
; Called under a catch by bbox. COM output arrays are WCS, not OCS or INSERT local.
(defun mep2:bbox-body (obj / lo hi)
  (vla-GetBoundingBox obj 'lo 'hi)
  (list (mep2:com-value lo) (mep2:com-value hi)))
(defun mep2:point3-valid (p)
  (and (listp p) (= (length p) 3)
       (numberp (car p)) (numberp (cadr p)) (numberp (caddr p))))
(defun mep2:bbox-status (getterSucceeded validPoints)
  (cond ((not getterSucceeded) "unavailable")
        ((not validPoints) "invalid_result")
        (T "read")))
(defun mep2:bbox (e prefix / obj r status valid)
  (setq obj (vl-catch-all-apply 'vlax-ename->vla-object (list e)))
  (if (vl-catch-all-error-p obj)
    (setq r obj)
    (progn
      (setq r (vl-catch-all-apply 'mep2:bbox-body (list obj)))
      (vl-catch-all-apply 'vlax-release-object (list obj))))
  (setq valid
    (and (not (vl-catch-all-error-p r)) (listp r) (= (length r) 2)
         (mep2:point3-valid (car r)) (mep2:point3-valid (cadr r))
         (<= (caar r) (car (cadr r)))
         (<= (cadr (car r)) (cadr (cadr r)))
         (<= (caddr (car r)) (caddr (cadr r)))))
  (setq status (mep2:bbox-status (not (vl-catch-all-error-p r)) valid))
  (if (/= status "read")
    (progn
      (mep2:val (strcat prefix "bboxMin") nil)
      (mep2:val (strcat prefix "bboxMax") nil)
      (mep2:val (strcat prefix "bboxFrame") "unknown")
      (mep2:val (strcat prefix "bboxStatus") status)
      (mep2:val (strcat prefix "bboxError_RAW")
        (if (vl-catch-all-error-p r) (vl-catch-all-error-message r) "invalid WCS extents")))
    (progn
      (mep2:val (strcat prefix "bboxMin") (car r))
      (mep2:val (strcat prefix "bboxMax") (cadr r))
      (mep2:val (strcat prefix "bboxFrame") "WCS")
      (mep2:val (strcat prefix "bboxStatus") "read"))))
(defun mep2:layout-body (e d parent prefix / typ spec pair)
  (setq typ (cdr (assoc 0 d)))
  (mep2:val (strcat prefix "LayoutEntityHandle") (cdr (assoc 5 d)))
  (mep2:val (strcat prefix "LayoutEntityType") typ)
  (mep2:val (strcat prefix "ParentINSERTHandle") parent)
  (mep2:val (strcat prefix "AngleUnit") "radians")
  (if (= typ "MTEXT")
    (progn
      (mep2:val "Rotation" nil)
      (mep2:val "Rotation_Status" "not_interpreted_use_direction_vector")
      (mep2:val "DirectionFrame" "WCS")))
  (foreach spec (mep2:layout-spec typ)
    (setq pair (assoc (cadr spec) d))
    (mep2:val (strcat prefix (car spec)) (cdr pair))
    (mep2:val (strcat prefix (car spec) "_Status") (if pair "read" "absent_in_entget")))
  (foreach pair d
    (if (member (car pair) '(1 3 7 10 11 40 41 50 51 60 70 71 72 73 74 100 210))
      (mep2:val (strcat prefix "TextLayout_DXF") pair)))
  (if (= typ "ATTRIB")
    (progn
      (mep2:val (strcat prefix "Tag_RAW") (cdr (assoc 2 d)))
      (mep2:val (strcat prefix "Value_RAW") (mep2:text d))
      (mep2:val (strcat prefix "AttributeFlags_DXF70") (cdr (assoc 70 d)))
      (mep2:val (strcat prefix "VisibilityEvidence")
        (cond ((not (assoc 70 d)) "unknown")
              ((/= 0 (logand 1 (cdr (assoc 70 d)))) "attribute_invisible_flag")
              (T "attribute_not_flagged_hidden_not_final_visibility")))))
  (if (= typ "MTEXT") (mep2:val "rawMText" (mep2:text d)))
  (mep2:layout-position e d prefix)
  (mep2:bbox e prefix))
; Optional enrichment never increments the entity ReadErrorCount.
(defun mep2:text-layout (e d parent prefix / r)
  (mep2:out (strcat prefix "TextLayout_BEGIN"))
  (setq r (vl-catch-all-apply 'mep2:layout-body (list e d parent prefix)))
  (if (vl-catch-all-error-p r)
    (progn
      (mep2:val (strcat prefix "TextLayoutStatus") "error")
      (mep2:val (strcat prefix "TextLayoutError_RAW") (vl-catch-all-error-message r)))
    (mep2:val (strcat prefix "TextLayoutStatus") "completed_check_field_statuses"))
  (mep2:out (strcat prefix "TextLayout_END")))
(defun mep2:leader (e d / pair pts ref rd obj value prop label)
  (mep2:val "LeaderEvidenceVersion" "1")
  (mep2:val "LeaderScope" (if (= (cdr (assoc 410 d)) "Model") "ModelSpace top-level only" "out_of_scope"))
  (mep2:val "LeaderParentPath" (if (= (cdr (assoc 410 d)) "Model") "[]" "unresolved"))
  (mep2:val "LeaderCoordinateSystem" "WCS")
  (if (= (cdr (assoc 0 d)) "LEADER")
    (progn
      (foreach pair d (if (= (car pair) 10) (setq pts (cons (cdr pair) pts))))
      (setq pts (reverse pts))
      (mep2:val "LeaderVertexCount" (cdr (assoc 76 d)))
      (foreach pair pts (mep2:val "LeaderVertex_WCS" pair))
      (mep2:val "LeaderGeometryStatus" (if (and (>= (length pts) 2) (= (length pts) (cdr (assoc 76 d)))) "read" "unresolved"))
      (mep2:val "ArrowFlag_DXF71" (cdr (assoc 71 d)))
      (mep2:val "PathType_DXF72" (cdr (assoc 72 d)))
      (mep2:val "LeaderArrowStatus" (if (and pts (= 1 (cdr (assoc 71 d)))) "read" "unresolved"))
      (if (and pts (= 1 (cdr (assoc 71 d)))) (mep2:val "Arrow_WCS" (car pts)))
      (setq ref (cdr (assoc 340 d)))
      (if ref (setq rd (entget ref)))
      (if (and rd (= (cdr (assoc 410 rd)) "Model") (member (cdr (assoc 0 rd)) '("TEXT" "MTEXT")))
        (progn
          (mep2:val "LeaderAnnotationStatus" "resolved")
          (mep2:val "AnnotationHandle" (cdr (assoc 5 rd)))
          (mep2:val "AnnotationType" (cdr (assoc 0 rd))))
        (mep2:val "LeaderAnnotationStatus" "unresolved")))
    (progn
      (mep2:val "MLeaderCapabilityStatus" "partial")
      (mep2:val "LeaderGeometryStatus" "unresolved")
      (mep2:val "LeaderAnnotationStatus" "unresolved")
      (mep2:val "MLeaderBranchStatus" "raw_only_not_interpreted")
      (setq obj (vl-catch-all-apply 'vlax-ename->vla-object (list e)))
      (foreach prop '(ContentType TextString LeaderCount ContentBlockName)
        (setq label (cond ((= prop 'TextString) "TextString") ((= prop 'ContentType) "ContentType") ((= prop 'LeaderCount) "LeaderCount") (T "ContentBlockName")))
        (setq value (if (vl-catch-all-error-p obj) obj (vl-catch-all-apply 'vlax-get-property (list obj prop))))
        (if (vl-catch-all-error-p value)
          (progn
            (mep2:val (strcat "MLeader" label "_Status") "unavailable")
            (mep2:val (strcat "MLeader" label "_Error") (vl-catch-all-error-message value)))
          (progn
            (mep2:val (strcat "MLeader" label "_Status") "read")
            (mep2:val (strcat "MLeader" label) value))))))
  (foreach pair d
    (if (not (member (car pair) '(310 311 312 313 314 315 316 317 318 319))) (mep2:val "Raw_DXF" pair))))

; Style evidence is separate from geometry and from semantic admission.
; Return (status value source); never synthesize absent DXF defaults.
(defun mep2:style-read (d code obj prop / pair value)
  (setq pair (if code (assoc code d)))
  (cond
    (pair (list "read" (cdr pair) (strcat "DXF:" (itoa code))))
    ((and obj prop)
      (setq value (vl-catch-all-apply 'vlax-get-property (list obj prop)))
      (if (vl-catch-all-error-p value)
        (list "unavailable" nil (strcat "COM:" (vl-symbol-name prop)))
        (list "read" value (strcat "COM:" (vl-symbol-name prop)))))
    (T (list "missing" nil (if code (strcat "DXF:" (itoa code)) "not_available")))))
(defun mep2:style-field (name result)
  (mep2:val (strcat "Style." name ".Status") (car result))
  (if (= (car result) "read") (mep2:val (strcat "Style." name ".Value") (cadr result)))
  (mep2:val (strcat "Style." name ".Source") (caddr result)))
(defun mep2:style-mode (r kind / v mode)
  (if (/= (car r) "read") r
    (progn
      (setq v (cadr r))
      (setq mode
        (cond
          ((= kind "color") (cond ((= v 256) "ByLayer") ((= v 0) "ByBlock") (T "explicit_aci")))
          ((= kind "linetype") (cond ((= (strcase v) "BYLAYER") "ByLayer") ((= (strcase v) "BYBLOCK") "ByBlock") (T "explicit")))
          ((= kind "weight") (cond ((= v -1) "ByLayer") ((= v -2) "ByBlock") ((= v -3) "default") (T "explicit")))))
      (list "read" mode (caddr r)))))
(defun mep2:style-bool (r / v)
  (if (/= (car r) "read") r
    (progn (setq v (cadr r))
      (list "read" (if (or (= v :vlax-true) (= v T)) "true" "false") (caddr r)))))
(defun mep2:style-color (prefix d obj / aci rgb book mode)
  (setq aci (mep2:style-read d 62 obj 'Color))
  (if (and (= prefix "layer_") (= (car aci) "read") (< (cadr aci) 0))
    (setq aci (list "read" (abs (cadr aci)) "DXF:62 magnitude; signed raw retained")))
  (setq rgb (mep2:style-read d 420 nil nil) book (mep2:style-read d 430 nil nil))
  (setq mode (cond ((= (car rgb) "read") (list "read" "explicit_truecolor" "DXF:420"))
    ((= (car book) "read") (list "read" "colorbook" "DXF:430"))
    (T (mep2:style-mode aci "color"))))
  (if (= (car rgb) "read")
    (setq rgb (list "read" (list (logand 255 (lsh (cadr rgb) -16)) (logand 255 (lsh (cadr rgb) -8)) (logand 255 (cadr rgb))) "DXF:420 RGB decode")))
  (mep2:style-field (strcat prefix "color_mode") mode)
  (mep2:style-field (strcat prefix "aci") aci)
  (mep2:style-field (strcat prefix "truecolor_rgb") rgb)
  (mep2:style-field (strcat prefix "colorbook_name") book))
(defun mep2:raw-style (e d / obj le ld lo r lt lw p flags)
  (mep2:val "StyleEvidenceVersion" "1")
  (setq obj (vl-catch-all-apply 'vlax-ename->vla-object (list e)))
  (if (vl-catch-all-error-p obj) (setq obj nil))
  (foreach p d (if (member (car p) '(6 8 48 60 62 70 370 420 430 440)) (mep2:val "StyleRawEntityDXF" p)))
  (mep2:style-color "entity_" d obj)
  (setq lt (mep2:style-read d 6 obj 'Linetype) lw (mep2:style-read d 370 obj 'Lineweight))
  (mep2:style-field "entity_linetype" lt)
  (mep2:style-field "entity_linetype_mode" (mep2:style-mode lt "linetype"))
  (mep2:style-field "entity_linetype_scale" (mep2:style-read d 48 obj 'LinetypeScale))
  (mep2:style-field "entity_lineweight" lw)
  (mep2:style-field "entity_lineweight_mode" (mep2:style-mode lw "weight"))
  (setq r (mep2:style-read d 60 obj 'Visible))
  (if (and (assoc 60 d) (= (car r) "read"))
    (setq r (list "read" (if (= (cadr r) 0) "true" "false") "DXF:60"))
    (setq r (mep2:style-bool r)))
  (mep2:style-field "entity_visibility" r)
  (setq le (tblobjname "LAYER" (cdr (assoc 8 d))) ld (if le (entget le)))
  (setq lo (if le (vl-catch-all-apply 'vlax-ename->vla-object (list le))))
  (if (vl-catch-all-error-p lo) (setq lo nil))
  (mep2:val "StyleLayerHandle" (cdr (assoc 5 ld)))
  (foreach p ld (if (member (car p) '(2 6 62 70 290 370 420 430 440)) (mep2:val "StyleRawLayerDXF" p)))
  (mep2:style-field "layer_name" (mep2:style-read ld 2 lo 'Name))
  (mep2:style-color "layer_" ld lo)
  (mep2:style-field "layer_linetype" (mep2:style-read ld 6 lo 'Linetype))
  (mep2:style-field "layer_lineweight" (mep2:style-read ld 370 lo 'Lineweight))
  (setq r (mep2:style-read ld 62 nil nil))
  (if (= (car r) "read")
    (setq r (list "read" (if (< (cadr r) 0) "false" "true") "DXF:62 sign"))
    (setq r (mep2:style-bool (mep2:style-read nil nil lo 'LayerOn))))
  (mep2:style-field "layer_on" r)
  (foreach p '(("layer_frozen" 1 Freeze) ("layer_locked" 4 Lock))
    (setq flags (assoc 70 ld))
    (setq r (if flags (list "read" (if (/= 0 (logand (cadr p) (cdr flags))) "true" "false") "DXF:70 bit")
      (mep2:style-bool (mep2:style-read nil nil lo (caddr p)))))
    (mep2:style-field (car p) r))
  (setq r (mep2:style-read ld 290 lo 'Plottable))
  (if (assoc 290 ld) (setq r (list "read" (if (= (cadr r) 0) "false" "true") "DXF:290")) (setq r (mep2:style-bool r)))
  (mep2:style-field "layer_plottable" r)
  ; No undocumented transparency getter or encoded flag interpretation.
  (mep2:style-field "layer_transparency" (list "unsupported" nil "raw DXF:440 retained if exposed; effective alpha not decoded"))
  (if obj (vl-catch-all-apply 'vlax-release-object (list obj)))
  (if lo (vl-catch-all-apply 'vlax-release-object (list lo))))

(defun mep2:details (e d / typ pair pts p z sub sd flags obj b bd styleResult)
  (setq typ (cdr (assoc 0 d)))
  (mep2:val "ObjectName" (mep2:class e))
  (mep2:val "Normal_DXF210" (cdr (assoc 210 d)))
  (if full
    (progn
      (setq styleResult (vl-catch-all-apply 'mep2:raw-style (list e d)))
      (mep2:val "StyleAcquisitionStatus" (if (vl-catch-all-error-p styleResult) "unavailable" "completed_check_field_statuses"))
      (if (vl-catch-all-error-p styleResult) (mep2:val "StyleAcquisitionError" (vl-catch-all-error-message styleResult)))))
  (cond
    ((member typ '("LEADER" "MLEADER" "MULTILEADER")) (mep2:leader e d))
    ((= typ "LINE")
      (mep2:val "Start_WCS" (cdr (assoc 10 d)))
      (mep2:val "End_WCS" (cdr (assoc 11 d))))
    ((= typ "LWPOLYLINE")
      (setq z (if (assoc 38 d) (cdr (assoc 38 d)) 0.0))
      (mep2:val "Flags_DXF70" (cdr (assoc 70 d)))
      (mep2:val "Closed" (= 1 (logand 1 (cdr (assoc 70 d)))))
      (mep2:val "Elevation" z)
      (foreach pair d
        (cond
          ((= (car pair) 10)
            (setq p (list (cadr pair) (caddr pair) z))
            (setq pts (cons p pts))
            (mep2:point "Vertex" p e))
          ((member (car pair) '(40 41 42 43))
            (mep2:val "Width_or_bulge_DXF" pair))))
      (setq pts (reverse pts))
      (mep2:point "FirstVertex" (car pts) e)
      (mep2:point "LastVertex" (last pts) e)
      (mep2:out "Closed paths connect last vertex to first; bulge belongs to preceding vertex."))
    ((= typ "POLYLINE")
      (mep2:val "StylePolylineFlags" (cdr (assoc 70 d)))
      (mep2:val "StylePolylineDefaultStartWidth" (cdr (assoc 40 d)))
      (mep2:val "StylePolylineDefaultEndWidth" (cdr (assoc 41 d)))
      (setq flags (if (assoc 70 d) (cdr (assoc 70 d)) 0))
      (mep2:val "Flags_DXF70" flags)
      (mep2:val "HeaderPoint_DXF10" (cdr (assoc 10 d)))
      (mep2:val "Closed" (= 1 (logand 1 flags)))
      (mep2:out "Raw VERTEX records follow; mesh/polyface and fitted curves are not interpreted as cable paths.")
      (setq sub (entnext e))
      (while (and sub (/= "SEQEND" (cdr (assoc 0 (setq sd (entget sub))))))
        (mep2:val "Subentity_DXF" sd)
        (if (= "VERTEX" (cdr (assoc 0 sd)))
          (progn
            (setq p (cdr (assoc 10 sd)))
            (setq pts (cons p pts))
            (cond
              ((/= 0 (logand flags 80)) (mep2:out "Mesh/polyface: raw coordinates only."))
              ((/= 0 (logand flags 8)) (mep2:val "Vertex_WCS" p))
              (T (mep2:point "Vertex" (list (car p) (cadr p) (caddr (cdr (assoc 10 d)))) e)))))
        (setq sub (entnext sub)))
      (setq pts (reverse pts))
      (mep2:val "FirstVertex_RAW" (car pts))
      (mep2:val "LastVertex_RAW" (last pts)))
    ((= typ "INSERT")
      (mep2:val "BlockName" (cdr (assoc 2 d)))
      (mep2:point "Insertion" (cdr (assoc 10 d)) e)
      (foreach pair d
        (if (member (car pair) '(41 42 43 50 70 71 44 45))
          (mep2:val "BlockTransform_or_Array_DXF" pair)))
      (setq b (tblsearch "BLOCK" (cdr (assoc 2 d))))
      (mep2:val "BlockFlags_DXF70" (cdr (assoc 70 b)))
      (mep2:val "XrefPath_DXF1" (cdr (assoc 1 b)))
      (if (= 1 (cdr (assoc 66 d)))
        (progn
          (setq sub (entnext e))
          (while (and sub (/= "SEQEND" (cdr (assoc 0 (setq sd (entget sub))))))
            (if (= "ATTRIB" (cdr (assoc 0 sd)))
              (progn
                (mep2:val "AttributeTag" (cdr (assoc 2 sd)))
                (mep2:val "AttributeText_RAW" (mep2:text sd))
                (mep2:val "AttributeLayer" (cdr (assoc 8 sd)))
                (mep2:val "Attribute_DXF" sd)
                (if full (mep2:text-layout sub sd (cdr (assoc 5 d)) "AttributeLayout."))))
            (setq sub (entnext sub)))))
      ; Constant attribute definitions are in block-local coordinates.
      (setq sub (cdr (assoc -2 b)))
      (while sub
        (setq sd (entget sub))
        (if (and (= "ATTDEF" (cdr (assoc 0 sd)))
                 (/= 0 (logand 2 (cdr (assoc 70 sd)))))
          (mep2:val "ConstantAttributeDefinition_BLOCK_LOCAL" sd))
        (setq sub (entnext sub)))
      (mep2:out "Nested block geometry is NOT expanded; block-local geometry is not counted as ModelSpace entities.")
      (if full (mep2:dynamic e)))
    ((member typ '("TEXT" "MTEXT"))
      (mep2:val "Text_RAW" (mep2:text d))
      (if (= typ "MTEXT")
        (mep2:val "Insertion_WCS" (cdr (assoc 10 d)))
        (progn
          (mep2:point "Insertion" (cdr (assoc 10 d)) e)
          (mep2:point "Alignment" (cdr (assoc 11 d)) e)))
      (mep2:out "Text formatting/field expressions are preserved, not evaluated.")
      (if full (mep2:text-layout e d nil "")))
    ((= typ "ACAD_TABLE")
      (foreach pair d
        (if (not (member (car pair) '(310 311 312 313 314 315 316 317 318 319)))
          (mep2:val "Raw_DXF" pair)))
      (if full (mep2:table e)))
    (T
      (mep2:out "UNPARSED_TYPE: identity and non-binary DXF fields only; no semantic inference.")
      (foreach pair d
        (if (not (member (car pair) '(310 311 312 313 314 315 316 317 318 319)))
          (mep2:val "Raw_DXF" pair))))))

; TABLE getters are observations, not static-text/engineering approval.
(defun mep2:table-value (label fn args / value)
  (mep2:val (strcat label ".Source") (vl-prin1-to-string fn))
  (setq value (vl-catch-all-apply fn args))
  (if (vl-catch-all-error-p value)
    (progn (mep2:val (strcat label ".Status") "unavailable")
      (mep2:val (strcat label ".Error") (vl-catch-all-error-message value)) nil)
    (progn
      (setq value (vl-catch-all-apply 'mep2:com-value (list value)))
      (if (vl-catch-all-error-p value)
        (progn (mep2:val (strcat label ".Status") "conversion_error") nil)
        (progn (mep2:val (strcat label ".Value") value)
          (mep2:val (strcat label ".Status") "read") value)))))
(defun mep2:table-merge (obj row col / minRow maxRow minCol maxCol merged)
  (setq merged (vla-IsMergedCell obj row col 'minRow 'maxRow 'minCol 'maxCol))
  (if (= merged :vlax-true) (mep2:val "Cell.MergeRange" (list minRow maxRow minCol maxCol)))
  (if (= merged :vlax-true) -1 0))
(defun mep2:table-body (obj / rows cols row col entry)
  (setq rows (mep2:table-value "Table.Rows" 'vlax-get-property (list obj 'Rows)))
  (setq cols (mep2:table-value "Table.Columns" 'vlax-get-property (list obj 'Columns)))
  (mep2:table-value "Table.StyleName" 'vlax-get-property (list obj 'StyleName))
  (mep2:table-value "Table.InsertionPoint" 'vlax-get-property (list obj 'InsertionPoint))
  (mep2:val "Table.MultipleContents.Status" "unsupported")
  (mep2:val "Table.CellGeometry.Status" "unresolved")
  (if (and (= (type rows) 'INT) (= (type cols) 'INT) (> rows 0) (> cols 0) (<= (* rows cols) 100000))
    (progn
      (setq row 0)
      (repeat rows
        (mep2:val "Table.RowIndex" row)
        (mep2:table-value "Table.RowHeight" 'vla-GetRowHeight (list obj row))
        (setq col 0)
        (repeat cols
          (if (= row 0)
            (progn (mep2:val "Table.ColumnIndex" col)
              (mep2:table-value "Table.ColumnWidth" 'vla-GetColumnWidth (list obj col))))
          (mep2:out "TableCell_BEGIN")
          (mep2:val "Cell.Row" row) (mep2:val "Cell.Column" col)
          (foreach entry '(("Type" vla-GetCellType) ("ContentType" vla-GetContentType)
                          ("Text" vla-GetText) ("Empty" vla-IsEmpty) ("FieldId" vla-GetFieldId)
                          ("BlockId" vla-GetBlockTableRecordId) ("TextStyle" vla-GetCellTextStyle)
                          ("TextHeight" vla-GetCellTextHeight) ("Alignment" vla-GetCellAlignment))
            (mep2:table-value (strcat "Cell." (car entry)) (cadr entry) (list obj row col)))
          (mep2:table-value "Cell.Merged" 'mep2:table-merge (list obj row col))
          (mep2:val "Cell.FieldProvenance.Status" "missing")
          (mep2:out "TableCell_END")
          (setq col (1+ col)))
        (setq row (1+ row)))
      (mep2:out "TableEvidenceComplete=true"))
    (mep2:val "Table.AcquisitionError" "dimensions unavailable/invalid or cell limit exceeded")))
(defun mep2:table (e / obj result)
  (mep2:val "TableEvidenceVersion" "1") (mep2:out "TableEvidence_BEGIN")
  (setq obj (vl-catch-all-apply 'vlax-ename->vla-object (list e)))
  (if (vl-catch-all-error-p obj)
    (mep2:val "Table.AcquisitionError" (vl-catch-all-error-message obj))
    (progn
      (setq result (vl-catch-all-apply 'mep2:table-body (list obj)))
      (if (vl-catch-all-error-p result) (mep2:val "Table.AcquisitionError" (vl-catch-all-error-message result)))
      (vl-catch-all-apply 'vlax-release-object (list obj))))
  (mep2:bbox e "Table.")
  (mep2:out "TableEvidence_END"))

(defun mep2:read (full / *error* mep2:fh outputPath outputFileName proceed existing stage row layers layer ss i e d typ counts entry total errors result root filename allcounts)
  (defun *error* (msg)
    (princ (strcat "\nEntity acquisition stopped at stage [" (if stage stage "initialization") "]: " msg))
    (if mep2:fh
      (progn
        (vl-catch-all-apply 'write-line (list (strcat "INCOMPLETE_REPORT: " msg) mep2:fh))
        (vl-catch-all-apply 'close (list mep2:fh))
        (setq mep2:fh nil)))
    (princ))
  (vl-catch-all-apply 'vl-load-com nil)
  ; Use this script's folder when findfile can resolve it; otherwise choose manually.
  (setq root (findfile "Test-AutoCADEntities.lsp"))
  (setq filename (if full "MEP-full-entity-report.txt" "MEP-entity-report.txt"))
  (setq stage "getfiled")
  (setq outputPath (getfiled (strcat "Save read-only snapshot as " filename)
    (if root
      (strcat (vl-filename-directory root) "/local_test_data/" filename)
      (strcat (getvar "DWGPREFIX") filename)) "txt" 1))
  (setq proceed outputPath stage "path-validation")
  ; Only full mode adds absolute-path validation; never reconstruct the selection.
  (if (and full outputPath)
    (progn
      (princ (strcat "\nOutputPath = " outputPath))
      (if (not (or
        (and (>= (strlen outputPath) 3) (= (substr outputPath 2 1) ":") (member (substr outputPath 3 1) '("/" "\\")))
        (= (substr outputPath 1 2) "\\\\")
        (= (substr outputPath 1 2) "//")))
        (progn (princ "\nRejected: absolute output path required.") (setq proceed nil)))))
  (if proceed
    (progn
      (setq stage "filename-validation")
      (setq outputFileName (strcat (vl-filename-base outputPath) (if (vl-filename-extension outputPath) (vl-filename-extension outputPath) "")))
      (if full (princ (strcat "\nOutputFileName = " outputFileName)))
      (setq stage "existence-check")
      (if full
        (progn
          (setq existing (findfile outputPath))
          (princ (strcat "\nExists = " (if existing "YES" "NO")))
          (if existing
            (progn (princ (strcat "\nExisting snapshot protected:\n" existing)) (setq proceed nil)))))))
  (if proceed (setq stage "filename-validation"))
  (if proceed
    (if (/= (strcase outputFileName) (strcase filename))
      (princ (strcat "\nCancelled: report filename must be " filename))
      (progn
        (setq stage "open-output")
        (setq mep2:fh (if (= 0 (getvar "LISPSYS")) (open outputPath "w") (open outputPath "w" "utf8-bom")))
        (if (not mep2:fh) (progn (princ "\nCannot open report file.") (exit)))
        (mep2:out "MEP-Manager phase 2: READ-ONLY ENTITY REPORT")
        (if full
          (progn
            (mep2:val "ExtractorVersion" "2.6-table-cell-evidence-v1")
            (mep2:val "LineStyleContractVersion" "1")
            (mep2:val "TextLayoutContractVersion" "2.3-text-layout-metadata")
            (mep2:val "TextLayoutMetadata" "TEXT/MTEXT/attached ATTRIB; raw DXF plus optional WCS bbox; no layout interpretation")
            (mep2:val "BoundingBoxPolicy" "best-effort getter; independent status; failures do not increment ReadErrorCount")
            (mep2:val "DynamicBlockMetadata" "top-level INSERT getter-only; independent per-field status; no geometry expansion")
            (mep2:val "AcquisitionMode" "ModelSpaceTopLevelAllLayers")
            (mep2:val "AcquiredAtLocal" (getvar "CDATE"))
            (mep2:val "ModelSpaceTopLevel" "included")
            (mep2:val "AllLayers" "included; including off/frozen")
            (mep2:val "AttachedATTRIB" "included for selected INSERT; raw DXF")
            (mep2:val "ConstantATTDEF" "direct block definition only; block-local raw DXF")
            (mep2:val "BlockDefinitionRecursiveExpansion" "not included")
            (mep2:val "NestedBlocks" "not expanded")
            (mep2:val "XrefContents" "not expanded")
            (mep2:val "PaperSpaceLayouts" "not included")
            (mep2:val "ProxySemanticRecovery" "not included; identity/non-binary DXF only")
            (mep2:val "TableSemanticExtraction" "not included; raw non-binary DXF may contain cell values")
            (mep2:val "SnapshotPolicy" "new snapshot; no automatic evidence or confirmation migration")
            (mep2:val "FingerprintPolicy" "SHA-256 exact saved bytes externally; timestamp and runtime DXF references can differ between runs")))
        (mep2:val "DWG" (strcat (getvar "DWGPREFIX") (getvar "DWGNAME")))
        (mep2:val "INSUNITS" (getvar "INSUNITS"))
        (mep2:out "Coordinates are drawing units; no length calculation. No DWG write/save/cleanup/conversion.")
        (mep2:out "Real-valued coordinates use decimal notation with 6 fractional digits, including nested DXF records.")
        (if full
          (mep2:out "Scope: ModelSpace top-level entities on ALL layers; no professional candidate filtering. Not a complete DWG extraction.")
          (progn
            (mep2:out "Scope: ModelSpace top-level entities on candidate layers, including off/frozen layers.")
            (mep2:out "Layer matching: EQUIP-*, E-*, EP-*, CABLETRAY_*, WIRE-*, LWIRE, TEL_TEXT, TEL_SYMB; also prefixed names.")))
        (mep2:out "Nested geometry/XREF contents are NOT recursively scanned. Zero does not prove absence in nested blocks.")
        (mep2:out "ObjectName uses optional in-process ActiveX; failure is recorded without stopping native DXF reads.")
        (setq stage "entity-acquisition")
        (setq row (tblnext "LAYER" T) total 0 errors 0)
        (while row
          (setq layer (cdr (assoc 2 row)))
          (if (or full (wcmatch (strcase layer) "*EQUIP-*,*E-*,*EP-*,*CABLETRAY_*,*WIRE-*,*LWIRE,*TEL_TEXT,*TEL_SYMB"))
            (setq layers (cons layer layers)))
          (setq row (tblnext "LAYER")))
        (foreach layer (reverse layers)
          (princ (strcat "\nReading layer: " layer))
          (mep2:val "LAYER_BEGIN" layer)
          ; Escape wildcard characters so ssget matches this exact layer name.
          (setq root "")
          (foreach i (vl-string->list layer)
            (if (member i '(35 64 46 42 63 126 91 93 45 44 96))
              (setq root (strcat root "`")))
            (setq root (strcat root (chr i))))
          (setq ss (ssget "_X" (list (cons 8 root) '(410 . "Model"))))
          (setq i 0 counts nil)
          (if ss
            (repeat (sslength ss)
              (setq e (ssname ss i) i (1+ i))
              (setq d (vl-catch-all-apply 'entget (list e)))
              (if (or (vl-catch-all-error-p d) (not d))
                (progn
                  (setq errors (1+ errors))
                  (mep2:val "ENTITY_UNREADABLE" (vl-prin1-to-string e))
                  (mep2:val "Error" (if (vl-catch-all-error-p d) (vl-catch-all-error-message d) "entget returned nil")))
                (progn
                  (setq typ (cdr (assoc 0 d)) entry (assoc typ counts))
                  (setq counts (if entry (subst (cons typ (1+ (cdr entry))) entry counts) (cons (cons typ 1) counts)))
                  (if full
                    (progn
                      (setq entry (assoc typ allcounts))
                      (setq allcounts (if entry (subst (cons typ (1+ (cdr entry))) entry allcounts) (cons (cons typ 1) allcounts)))))
                  (mep2:val "EntityHandle" (cdr (assoc 5 d)))
                  (mep2:val "DXF_Type" typ)
                  (mep2:val "Layer" (cdr (assoc 8 d)))
                  (setq result (vl-catch-all-apply 'mep2:details (list e d)))
                  (if (vl-catch-all-error-p result)
                    (progn (setq errors (1+ errors))
                      (mep2:val "DETAIL_ERROR" (vl-catch-all-error-message result)))))))
            )
          (setq total (+ total i))
          (mep2:val "LayerEntityCount" i)
          (mep2:val "TypeCounts_DXF" (reverse counts))
          (mep2:out "LAYER_END")
          (setq ss nil))
        (mep2:val (if full "ObservedLayerCount" "CandidateLayerCount") (length layers))
        (if full (mep2:val "GlobalTypeCounts_DXF" (reverse allcounts)))
        (mep2:val "SelectedEntityTotal" total)
        (mep2:val "ReadErrorCount" errors)
        (mep2:out "END_OF_REPORT: scan finished. Inspect errors and scope limitations before interpreting results.")
        (setq stage "close-output")
        (close mep2:fh) (setq mep2:fh nil)
        (princ (strcat "\nReport saved: " outputPath "\nEntities: " (itoa total) "; errors: " (itoa errors)))))
    (princ "\nCancelled. No report written."))
  (princ))
(defun c:MEPENTITYREAD () (mep2:read nil))
(defun c:MEPFULLREAD () (mep2:read T))
(princ "\nLoaded. MEPENTITYREAD: candidate layers. MEPFULLREAD: all-layer ModelSpace top-level snapshot.")
(princ)
